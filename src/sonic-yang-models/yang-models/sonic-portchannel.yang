module sonic-portchannel {

    yang-version 1.1;

    namespace "http://github.com/sonic-net/sonic-portchannel";
    prefix lag;

    import sonic-types {
        prefix stypes;
    }

    import ietf-yang-types {
        prefix yang;
    }

    import sonic-port {
        prefix port;
        revision-date 2019-07-01;
    }

    import sonic-vrf {
        prefix vrf;
    }

    import sonic-extension {
        prefix sonic-ext;
    }

    description "Link Aggregation Group (LAG/PortChannel) configuration using LACP";

    revision 2026-08-03 {
        description "Add LACP fallback_timeout configuration on PORTCHANNEL";
    }

    revision 2026-07-29 {
        description "Add LACP active/passive mode configuration on PORTCHANNEL";
    }

    revision 2026-07-09 {
        description "Add LAG_TABLE and LAG_MEMBER_TABLE operational state containers";
    }

    revision 2025-06-24 {
        description "Add LACP System MAC address";
    }

    revision 2021-06-13 {
        description "Change min-links valid range from 1-128 to 1-1024";
    }

    revision 2021-03-31 {
        description "Add PortChannel Interface List with VRF attribute";
    }

    revision 2021-03-15 {
        description "Add SONiC PortChannel Interface model";
    }

    revision 2019-07-01 {
        description "First Revision";
    }

    typedef lag-type {
        type enumeration {
            enum LACP;
            enum STATIC;
        }
    }

    container sonic-portchannel {

        container PORTCHANNEL {

            description "PortChannel (LAG) interface configuration table";

            list PORTCHANNEL_LIST {

                description "Configuration entry for a PortChannel aggregate interface";

                key "name";

                sonic-ext:custom-validation ValidatePortChannelCreationDeletion;

                leaf name {
                    description "PortChannel interface name (e.g. PortChannel0001)";
                    type string {
                        pattern 'PortChannel[0-9]{1,4}';
                    }
                }

                leaf min_links {
                    description "Minimum number of active member links required for the PortChannel to be operationally up";
                    type uint16 {
                        range 1..1024;
                    }
                }

               leaf mode {
                   description "PortChannel SwitchPort Mode possible values are routed|access|trunk. Default value for mode is routed.";
                   type stypes:switchport_mode;

                }

                leaf description {
                    description "User-defined description for the PortChannel interface";
                    type string {
                        length 1..255;
                    }
                }

                leaf mtu {
                    description "Maximum transmission unit size in bytes";
                    type uint16 {
                        range 1..9216;
                    }
                }

                leaf admin_status {
                    description "Administrative state of the PortChannel interface";
                    mandatory true;
                    type stypes:admin_status;
                }

                leaf lacp_key {
                    description "LACP aggregation key; 'auto' derives it from the PortChannel name, or specify a value from 1 to 65535";
                    /* lacp key should be either auto or a integer in the range of 1 to 65535 */
                    /* When lacp_key is set to 'auto' the lacp key would be set to be the number */
                    /* on the end of the PortChannel name with a prefix of 1 */
                    type union {
                        type string {
                            pattern "auto";
                        }
                        type uint16 {
                            range 1..65535;
                        }
                    }
                }

                leaf tpid {
                    description "This leaf describes the possible TPID value that can be configured
                                to the specified portchannel if the HW supports TPID configuration. The possible
                                values are 0x8100, 0x9100, 0x9200, 0x88a8, and 0x88A8";
                    type stypes:tpid_type;
                }

                leaf fallback {
                    description "Enable LACP fallback feature";
                    type stypes:boolean_type;
                }

                leaf fallback_timeout {
                    description "Number of seconds to wait for LACP PDUs from the peer before
                                 falling back to a single active member port. The value may remain
                                 configured while fallback is disabled so it can be restored when
                                 fallback is re-enabled; defaults to 90 seconds when unset.";
                    must "../fallback = 'true' or ../fallback = 'True' or "
                       + "../fallback = 'false' or ../fallback = 'False'" {
                        error-message "fallback_timeout requires fallback to be configured.";
                        error-app-tag fallback-timeout-requires-fallback;
                    }
                    type uint16 {
                        range 1..65535;
                    }
                }

                leaf fast_rate {
                    description "Enable LACP fast rate";
                    type stypes:boolean_type;
                }

                leaf active {
                    description
                        "LACP activity mode for the aggregate interface. When true, the
                         local system transmits LACP PDUs (active mode). When false, the
                         local system waits for the peer to initiate LACP (passive mode).";
                    type stypes:boolean_type;
                }

                leaf system_mac {
                    description
                        "Optional override for the LACP system MAC address used by this PortChannel.
                         When set, this MAC is used as the LACP actor system identifier instead of the
                         device's default system MAC, which is useful for MC-LAG / EVPN multihoming
                         deployments that require peer devices to advertise a shared LACP system ID.
                         When unset, the device's default system MAC is used.";
                    type yang:mac-address;
                }

                leaf lag_type {
                    type lag-type;
                    description "Describes how the LAG is defined and managed; either statically or with LACP";
                }

            } /* end of list PORTCHANNEL_LIST */

        } /* end of container PORTCHANNEL */

        container PORTCHANNEL_MEMBER {

            description "Mapping of physical ports to PortChannel aggregate interfaces";

            list PORTCHANNEL_MEMBER_LIST {

                description "Association of a physical port as a member of a PortChannel";

                key "name port";

                leaf name {
                    description "Reference to the parent PortChannel interface";
                    type leafref {
                        path "/lag:sonic-portchannel/lag:PORTCHANNEL/lag:PORTCHANNEL_LIST/lag:name";
                    }
                }

                leaf port {
                    description "Reference to the physical port that is a member of this PortChannel";
                    /* key elements are mandatory by default */
                    type leafref {
                        path /port:sonic-port/port:PORT/port:PORT_LIST/port:name;
                    }
                }
            } /* end of list PORTCHANNEL_MEMBER_LIST */

        } /* end of container PORTCHANNEL_MEMBER */

        container PORTCHANNEL_INTERFACE {

            description "PortChannel interface L3 configuration including VRF binding and IP addressing";

            list PORTCHANNEL_INTERFACE_LIST {
                description "L3 configuration entry for a PortChannel interface";

                key "name";

                leaf name {
                    description "Reference to the PortChannel interface";
                    /* key elements are mandatory by default */
                    type leafref {
                        path "/lag:sonic-portchannel/lag:PORTCHANNEL/lag:PORTCHANNEL_LIST/lag:name";
                    }
                }

                leaf vrf_name {
                    description "VRF instance to which this PortChannel interface is bound";
                    type leafref {
                        path "/vrf:sonic-vrf/vrf:VRF/vrf:VRF_LIST/vrf:name";
                    }
                }

                leaf loopback_action {
                    description "Packet action when a packet ingress and gets routed on the same IP interface";
                    type stypes:loopback_action;
                }

		leaf nat_zone {
		    description "NAT Zone for the portchannel interface";
		    type uint8 {
		        range "0..3" {
			    error-message "Invalid nat zone for the portchannel interface.";
			    error-app-tag nat-zone-invalid;
			}
		    }
		    default "0";
		}
		leaf mpls {
			description "Enable/disable MPLS routing for the portchannel interface";
                        type enumeration {
				enum enable;
				enum disable;
			}
		}

		leaf ipv6_use_link_local_only {
			description "Enable/Disable IPv6 link local address on portchannel interface";
			type stypes:mode-status;
			default disable;
		}

		leaf ipv6_ra_suppress {
			description "When true, IPv6 router advertisements are not transmitted on this PortChannel interface";
			type stypes:boolean_type;
			default "false";
		}

		leaf ipv6_ra_interval {
			description "Interval between periodic IPv6 router advertisements, in seconds";
			type uint32;
			units seconds;
		}

		leaf ipv6_ra_lifetime {
			description "Router lifetime advertised in IPv6 router advertisements, in seconds";
			type uint32;
			units seconds;
		}

		leaf ipv6_ra_reachable_time {
			description "Reachable Time advertised in IPv6 router advertisements (OpenConfig reachable-time), in milliseconds";
			type uint32 {
				range "0..3600000";
			}
			units milliseconds;
		}

		leaf ipv6_ra_enable {
			description "When false, IPv6 router advertisements are not transmitted (OpenConfig enable)";
			type stypes:boolean_type;
			default "true";
		}

		leaf ipv6_ra_managed {
			description "Advertise the managed address configuration flag in IPv6 RAs (OpenConfig managed)";
			type stypes:boolean_type;
			default "false";
		}

		leaf ipv6_ra_other_config {
			description "Advertise the other configuration flag in IPv6 RAs (OpenConfig other-config)";
			type stypes:boolean_type;
			default "false";
		}

                leaf mac_addr {
                    description "Assign administrator-provided MAC address to Interface";
                    type yang:mac-address;
                }

            } /* end of list PORTCHANNEL_INTERFACE_LIST */

            list PORTCHANNEL_INTERFACE_IPPREFIX_LIST {

                description "IP address prefix assignment for a PortChannel interface";

                key "name ip_prefix";

                leaf name {
                    description "Reference to the PortChannel interface";
                    /* key elements are mandatory by default */
                    type leafref {
                        path "/lag:sonic-portchannel/lag:PORTCHANNEL/lag:PORTCHANNEL_LIST/lag:name";
                    }
                }

                leaf ip_prefix {
                    description "IPv4 or IPv6 address with prefix length assigned to the PortChannel interface";
                    /* key elements are mandatory by default */
                    type stypes:sonic-ip-prefix;
                }

		leaf ipv6_ra_prefix_valid_lifetime {
			description "Valid lifetime for this prefix in IPv6 RAs (OpenConfig valid-lifetime)";
			type uint32;
			units seconds;
		}

		leaf ipv6_ra_prefix_preferred_lifetime {
			description "Preferred lifetime for this prefix in IPv6 RAs (OpenConfig preferred-lifetime)";
			type uint32;
			units seconds;
		}

		leaf ipv6_ra_prefix_disable_autoconfig {
			description "When true, disable SLAAC for this prefix in IPv6 RAs (OpenConfig disable-autoconfiguration)";
			type stypes:boolean_type;
		}

		leaf ipv6_ra_prefix_enable_onlink {
			description "When true, mark this prefix on-link in IPv6 RAs (OpenConfig enable-onlink)";
			type stypes:boolean_type;
		}
            } /* end of list PORTCHANNEL_INTERFACE_IPPREFIX_LIST */

        } /* end of container PORTCHANNEL_INTERFACE */

        container LAG_TABLE {

            config false;

            description "Operational state of PortChannel (LAG) interfaces";

            list LAG_TABLE_LIST {

                description "Operational state entry for a PortChannel interface";

                key "name";

                leaf name {
                    description "PortChannel interface name";
                    type string;
                }

                leaf admin_status {
                    description "Administrative status of the PortChannel interface";
                    type stypes:admin_status;
                }

                leaf mtu {
                    description "Maximum transmission unit size in bytes";
                    type uint16 {
                        range 1..9216;
                    }
                }

                leaf active {
                    description "Whether the LAG is active";
                    type boolean;
                }

                leaf oper_status {
                    description "Operational status of the PortChannel interface";
                    type stypes:oper-status;
                }

                leaf speed {
                    description "Operational speed of the PortChannel interface in Mbps";
                    type uint64;
                }

                leaf traffic_disable {
                    description "Whether traffic is disabled on the PortChannel (used by MC-LAG)";
                    type boolean;
                }

            } /* end of list LAG_TABLE_LIST */

        } /* end of container LAG_TABLE */

        container LAG_MEMBER_TABLE {

            config false;

            description "Operational state of PortChannel member ports";

            list LAG_MEMBER_TABLE_LIST {

                description "Operational state entry for a PortChannel member port";

                key "name port";

                leaf name {
                    description "Reference to the parent PortChannel interface";
                    type leafref {
                        path "/lag:sonic-portchannel/lag:LAG_TABLE/lag:LAG_TABLE_LIST/lag:name";
                    }
                }

                leaf port {
                    description "Reference to the physical port that is a member of this PortChannel";
                    type leafref {
                        path /port:sonic-port/port:PORT/port:PORT_LIST/port:name;
                    }
                }

                leaf status {
                    description "Operational status of the PortChannel member port";
                    type string;
                }

            } /* end of list LAG_MEMBER_TABLE_LIST */

        } /* end of container LAG_MEMBER_TABLE */

    } /* end of container sonic-portchannel */

} /* end of module sonic-portchannel */
