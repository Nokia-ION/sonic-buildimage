module sonic-interface {

	yang-version 1.1;

	namespace "http://github.com/sonic-net/sonic-interface";
	prefix intf;

	import ietf-yang-types {
		prefix yang;
	}

	import sonic-types {
		prefix stypes;
	}

	import sonic-port {
		prefix port;
		revision-date 2019-07-01;
	}

	import sonic-vrf {
		prefix vrf;
	}
	
	import sonic-vnet {
		prefix svnet;
	}

	description "Physical Ethernet interface L3 configuration including IP addressing, VRF binding, and NAT zones";

	revision 2025-03-06 {
		description "Add leaf vnet_name";
	}

	revision 2021-03-30 {
		description "Modify the type of vrf name";
	}

	revision 2019-07-01 {
		description "First Revision";
	}

	container sonic-interface {

		container INTERFACE {

			description "Physical Ethernet interface L3 configuration table";

			list INTERFACE_LIST {

				description "Configuration entry for a physical Ethernet interface including VRF binding and interface properties";

				key "name";

				leaf name {
					description "Reference to a physical Ethernet port";
					type leafref {
						path /port:sonic-port/port:PORT/port:PORT_LIST/port:name;
					}
				}

				leaf vrf_name {
					description "VRF instance to which this interface is bound";
					type leafref {
						path "/vrf:sonic-vrf/vrf:VRF/vrf:VRF_LIST/vrf:name";
					}
				}
				
				leaf vnet_name {
					description "Reference to the name of a VNET in sonic-vnet model";
					type leafref {
						path "/svnet:sonic-vnet/svnet:VNET/svnet:VNET_LIST/svnet:name";
					}   
				}

				leaf nat_zone {
					description "NAT Zone for the interface";
					type uint8 {
						range "0..3" {
							error-message "Invalid nat zone for the interface.";
							error-app-tag nat-zone-invalid;
						}
					}
                                        default "0";
				}

				leaf mpls {
					description "Enable/disable MPLS routing for the interface";
					type enumeration {
						enum enable;
						enum disable;
					}
				}

				leaf ipv6_use_link_local_only {
					description "Enable/Disable IPv6 link local address on interface";
					type stypes:mode-status;
					default disable;
				}

				leaf ipv6_ra_suppress {
					description "When true, IPv6 router advertisements are not transmitted on this interface";
					type stypes:boolean_type;
					default "false";
				}

				leaf ipv6_ra_interval {
					description "Interval between periodic IPv6 router advertisements, in seconds";
					type uint32;
					units seconds;
				}

				leaf ipv6_ra_lifetime {
					description "Router lifetime advertised in IPv6 router advertisements, in seconds";
					type uint32;
					units seconds;
				}

				leaf ipv6_ra_reachable_time {
					description "Reachable Time advertised in IPv6 router advertisements (OpenConfig reachable-time), in milliseconds";
					type uint32 {
						range "0..3600000";
					}
					units milliseconds;
				}

				leaf ipv6_ra_enable {
					description "When false, IPv6 router advertisements are not transmitted (OpenConfig enable)";
					type stypes:boolean_type;
					default "true";
				}

				leaf ipv6_ra_managed {
					description "Advertise the managed address configuration flag in IPv6 RAs (OpenConfig managed)";
					type stypes:boolean_type;
					default "false";
				}

				leaf ipv6_ra_other_config {
					description "Advertise the other configuration flag in IPv6 RAs (OpenConfig other-config)";
					type stypes:boolean_type;
					default "false";
				}

				leaf mac_addr {
					description "Assign administrator-provided MAC address to Interface";
					type yang:mac-address;
				}

                leaf loopback_action {
                    description "Packet action when a packet ingress and gets routed on the same IP interface";
                    type stypes:loopback_action;
                }

				leaf proxy_arp {
					description "Enable or disable proxy ARP on the interface";
					type string {
						pattern "enabled|disabled";
					}
				}
			}
			/* end of INTERFACE_LIST */

			list INTERFACE_IPPREFIX_LIST {

				description "IP address prefix assignment for a physical Ethernet interface";

				key "name ip-prefix";

				leaf name {
					description "Reference to a physical Ethernet port that must also exist in INTERFACE_LIST";
					/* This node must be present in INTERFACE_LIST */
					must "(current() = ../../INTERFACE_LIST[name=current()]/name)"
					{
						error-message "Must condition not satisfied, Try adding PORT: {}, Example: 'Ethernet0': {}";
					}

					type leafref {
						path /port:sonic-port/port:PORT/port:PORT_LIST/port:name;
					}
				}

				leaf ip-prefix {
					description "IPv4 or IPv6 address with prefix length assigned to the interface";
					type union {
						type stypes:sonic-ip4-prefix;
						type stypes:sonic-ip6-prefix;
					}
				}

				leaf scope {
					description "Address scope indicating global or link-local reachability";
					type enumeration {
						enum global;
						enum local;
					}
				}

				leaf family {
					description "IP address family, must match the format of ip-prefix";

					/* family leaf needed for backward compatibility
					   Both ip4 and ip6 address are string in IETF RFC 6021,
					   so must statement can check based on : or ., family
					   should be IPv4 or IPv6 according.
					 */

					must "(contains(../ip-prefix, ':') and current()='IPv6') or
						(contains(../ip-prefix, '.') and current()='IPv4')";
					type stypes:ip-family;
				}

				leaf ipv6_ra_prefix_valid_lifetime {
					description "Valid lifetime for this prefix in IPv6 RAs (OpenConfig valid-lifetime)";
					type uint32;
					units seconds;
				}

				leaf ipv6_ra_prefix_preferred_lifetime {
					description "Preferred lifetime for this prefix in IPv6 RAs (OpenConfig preferred-lifetime)";
					type uint32;
					units seconds;
				}

				leaf ipv6_ra_prefix_disable_autoconfig {
					description "When true, disable SLAAC for this prefix in IPv6 RAs (OpenConfig disable-autoconfiguration)";
					type stypes:boolean_type;
				}

				leaf ipv6_ra_prefix_enable_onlink {
					description "When true, mark this prefix on-link in IPv6 RAs (OpenConfig enable-onlink)";
					type stypes:boolean_type;
				}
			}
			/* end of INTERFACE_IPPREFIX_LIST */

		}
		/* end of INTERFACE container */
	}
}
