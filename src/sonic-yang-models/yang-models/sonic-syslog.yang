module sonic-syslog {

    yang-version 1.1;

    namespace "http://github.com/sonic-net/sonic-system-syslog";
    prefix syslog;

    import ietf-inet-types {
        prefix inet;
    }

    import sonic-mgmt_vrf {
        prefix mvrf;
    }

    import sonic-vrf {
        prefix vrf;
    }

    import sonic-feature {
        prefix feature;
    }

    description "Remote syslog server and logging configuration YANG module for SONiC OS.";

    revision 2026-08-21 {
        description "Add TLS protocol and per-server tls_profile_id for remote syslog.";
    }

    revision 2022-04-18 {
        description "Initial revision.";
    }

    typedef vrf-device {
        description "Represents syslog VRF device";
        type enumeration {
            enum default;
            enum mgmt;
        }
    }

    typedef syslog-rate-limit-interval {
        description "Message rate limit interval in second";
        type uint32 {
            range 0..2147483647;
        }
    }

    typedef syslog-rate-limit-burst {
        description "Message rate limit burst in message count";
        type uint32 {
            range 0..2147483647;
        }
    }

    typedef log-format {
        description "Represents syslog log format";
        type enumeration {
            enum welf;
            enum standard;
        }
    }

    typedef rsyslog-protocol {
        description
            "The protocol to send logs to a remote server.
             tls implies TCP plus the rsyslog ossl stream driver.";
        type enumeration {
            enum tcp;
            enum udp;
            enum tls;
        }
    }

    typedef syslog-filter-type {
        description "The filter type";
        type enumeration {
            enum include;
            enum exclude;
        }
    }

    typedef rsyslog-severity {
        description "Minimum syslog severity level for log forwarding.";
        type enumeration {
            enum none;
            enum debug;
            enum info;
            enum notice;
            enum warn;
            enum error;
            enum crit;
        }
    }


    container sonic-syslog {

        container SYSLOG_SERVER {

            description "Remote syslog server destination configuration.";

            list SYSLOG_SERVER_LIST {
                description "A remote syslog server entry identified by address.";
                key "server_address";

                leaf server_address {
                    description "Syslog server IP address";
                    type inet:host;
                }

                leaf source {
                    description "Syslog source IP address";
                    type inet:ip-address;
                    must "(contains(current(), '.') and contains(../server_address, '.'))
                    or (contains(current(), ':') and contains(../server_address, ':'))";
                }

                leaf port {
                    description "Syslog server UDP port";
                    type inet:port-number;
                }

                leaf vrf {
                    description "Syslog VRF device";
                    type union {
                        type leafref {
                            path "/vrf:sonic-vrf/vrf:VRF/vrf:VRF_LIST/vrf:name";
                        }
                        type vrf-device;
                    }
                    must "(current() != 'mgmt')
                    or (/mvrf:sonic-mgmt_vrf/mvrf:MGMT_VRF_CONFIG/mvrf:vrf_global/mvrf:mgmtVrfEnabled = 'true')";
                }

                leaf filter {
                    description "Syslog filter type";
                    type syslog-filter-type;
                }

                leaf filter_regex {
                    description "Filter regex";
                    type string {
                        pattern '[^\n\r]+';
                    }
                }

                leaf protocol {
                    description "The protocol to send logs to remote server";
                    type rsyslog-protocol;
                    must "(current() != 'tls') or ../tls_profile_id" {
                        error-message "tls_profile_id is required when protocol is tls";
                    }
                }

                leaf transport_security {
                    description
                        "When true, forward this server over TLS (same as protocol tls).
                         Kept for OpenConfig transport-security mapping.";
                    type boolean;
                    must "(current() != 'true') or ../tls_profile_id" {
                        error-message "tls_profile_id is required when transport_security is true";
                    }
                }

                leaf tls_profile_id {
                    description
                        "gNSI Certz SSL profile id whose PEMs were installed under
                         /etc/sonic/ssl-certs/<id>/. Required when protocol is tls.
                         Must not be gnxi (the gNMI listener profile).";
                    type string {
                        pattern '[A-Za-z0-9._-]+';
                    }
                    must "current() != 'gnxi'" {
                        error-message "gnxi is the gNMI listener profile and cannot be used for syslog";
                    }
                }

                leaf severity {
                    description "Limit the severity to send logs to remote server";
                    type rsyslog-severity;
                }

                leaf facility {
                    description "Syslog facility for filtering logs forwarded to this server";
                    type string;
                }

            }
            /* end of list SYSLOG_SERVER_LIST */
        }
        /* end of container SYSLOG_SERVER */

        container SYSLOG_CONFIG {

            description "Global syslog daemon configuration.";

            container GLOBAL {
                description "Global syslog rate limiting, format, and severity settings.";
                leaf rate_limit_interval {
                    type syslog-rate-limit-interval;
                    description "Rate limiting interval in seconds for syslog messages.";
                }

                leaf rate_limit_burst {
                    type syslog-rate-limit-burst;
                    description "Maximum burst of syslog messages allowed per rate limit interval.";
                }

                leaf format {
                    description "Log format";
                    type log-format;
                    default standard;
                }

                leaf welf_firewall_name {
                    description "WELF format Firewall name";
                    type string {
                        pattern '[^\n\r"\\%]*';
                    }
                    must "(../format != 'standard')";
                }

                leaf severity {
                    type rsyslog-severity;
                    default notice;
                    description "Minimum severity level for local syslog messages.";
                }

                leaf src_intf {
                    type string;
                    description
                        "Global source interface (e.g. Loopback0) whose IP address is
                         used as the source address for remote syslog forwarding.
                         Equivalent to EOS 'logging source-interface'.";
                }

            }
            /* end of list SYSLOG_CONFIG_LIST */
        }
        /* end of container SYSLOG_CONFIG */

        container SYSLOG_CONFIG_FEATURE {

            description "Per-service syslog rate limiting configuration.";

            list SYSLOG_CONFIG_FEATURE_LIST {
                description "Per-service syslog rate limit entry.";
                key "service";

                leaf service {
                    description "Service name";
                    type leafref {
                        path "/feature:sonic-feature/feature:FEATURE/feature:FEATURE_LIST/feature:name";
                    }
                }

                leaf rate_limit_interval {
                    type syslog-rate-limit-interval;
                    description "Per-service rate limiting interval in seconds.";
                }

                leaf rate_limit_burst {
                    type syslog-rate-limit-burst;
                    description "Per-service maximum burst of syslog messages per interval.";
                }
            }
            /* end of list SYSLOG_CONFIG_FEATURE_LIST */
        }
        /* end of container SYSLOG_CONFIG_FEATURE */
    }
    /* end of container sonic-syslog */
}
/* end of module sonic-syslog */
